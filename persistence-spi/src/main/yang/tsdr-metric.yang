/*
 * Copyright (c) 2016 Cisco Systems,  Inc. and others.  All rights reserved.
 *
 * This program and the accompanying materials are made available under the
 * terms of the Eclipse Public License v1.0 which accompanies this distribution,
 * and is available at http://www.eclipse.org/legal/epl-v10.html
 */
module tsdr-metric-data {

    yang-version 1;

    namespace "opendaylight:tsdr:metric:data";

    prefix tsdr-metric-data;
    import TSDR { prefix TSDR; revision-date 2015-02-19; }

    contact
      "YuLing Chen <yuling_c@dell.com>, Sharon Aicler <saichler@cisco.com>";

    description
      "YANG definition of TSDR Data Model.";

    revision "2016-03-25" {
      description
        "TSDR Metric Data Model.";
    }

    typedef AggregationGranularity {
        description
            "Granularity of data aggregation.";
        type enumeration {
            enum 15_MIN;
            enum 30_MIN;
            enum HOURLY;
            enum DAILY;
            enum WEEKLY;
            enum MONTHLY;
            enum YEARLY;
        }
    }

    typedef AggregationType {
        description
            "Aggregation function type.";
        type enumeration {
            enum MIN;
            enum MAX;
            enum MEAN;
            enum MEDIAN;
        }
    }

    grouping TSDRMetric{
        uses TSDR:TSDRRecord;
        leaf MetricName {
            description
                "The name of the metric.";
            type string;
        }
        leaf MetricValue {
            description
                "The value of the metric.";
            type decimal64{
                fraction-digits 4;
            }
        }
        leaf TimeStamp {
            description
                "The time stamp of the data when it was collected.";
            type int64;
        }
    }

    rpc storeTSDRMetricRecord {
        description
            "The API to store a list of TSDRMetricRecord.";
             input {
                 list TSDRMetricRecord{
                     uses TSDRMetric;
                 }
             }
    }

    rpc getTSDRMetrics{
       description
            "The API to retrieve a list of TSDRRecord with specified category, start time, and end time.";
        input {
            leaf TSDRDataCategory {
                description
                    "The category of the TSDR data.";
                type string;
            }
            leaf start_time{
                description
                    "The start time of the TSDR data.";
               type int64;
            }
            leaf end_time{
                description
                    "The end time of the TSDR data.";
               type int64;
            }
        }
        output {
            list Metrics {
                uses TSDRMetric;
            }
        }
    }

    grouping TSDRAggregatedMetric{
        leaf MetricValue {
            description
                "The value of the aggregated metric.";
            type decimal64{
                fraction-digits 4;
            }
        }
        leaf TimeStamp {
            description
                "The start of the interval containing the aggregated metric.";
            type int64;
        }
    }

    list TSDRAggregationMetric{
        uses TSDRMetric;
        description
            "Aggregated TSDR Metric data.";
        leaf MinValue {
            description
                "Metric min value over the last aggregation period.";
            type decimal64 {
                fraction-digits 4;
            }
        }
        leaf MaxValue {
            description
                "metric max value over the last aggregation period.";
            type decimal64 {
                fraction-digits 4;
            }
        }
        leaf AvgValue {
            description
                "metric avg value over the last aggregation period.";
            type decimal64 {
                fraction-digits 4;
            }
        }
        leaf TSDRAggregationGranularity{
            description
                "Aggregation granularity.";
            type AggregationGranularity;
        }
    }

    list LatestMetric {
        description
            "Metrics data that was collected in the latest collection cycle.
            For example,if the metrics data is collected every 1 minute, this
            data structure would contain the metric values in the last minute.
            This data structure is provided for convenience and performance
            optimization for frequent queries on the metrics data collected
            in the latest cycle.";
        uses TSDR:TSDRRecord;
        leaf Name {
            description
                "Name of the metric.";
            type string;
        }
        leaf Value {
            description
                "Value of the metric.";
            type decimal64 {
                fraction-digits 4;
            }
        }
    }

    rpc getTSDRAggregatedMetrics{
       description
            "Retrieves the list of TSDRRecord with the specified category, start time, and end time, groups the values by the given interval, and aggregates the results using the given aggregation function.";
        input {
            leaf TSDRDataCategory {
                description
                    "The category of the TSDR data.";
                type string;
            }
            leaf start_time{
                description
                    "The start time of the TSDR data.";
               type int64;
            }
            leaf end_time{
                description
                    "The end time of the TSDR data.";
               type int64;
            }
            leaf interval{
                description
                    "Size of the interval in milliseconds by which the metris will be grouped for aggregation.";
               type int64;
            }
            leaf aggregation{
                description
                    "Aggregation function.";
               type AggregationType;
            }
        }
        output {
            list AggregatedMetrics {
                uses TSDRAggregatedMetric;
            }
        }
    }
}
