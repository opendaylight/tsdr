/*
 * Copyright (c) 2015 Dell Inc. and others.  All rights reserved.
 *
 * This program and the accompanying materials are made available under the
 * terms of the Eclipse Public License v1.0 which accompanies this distribution,
 * and is available at http://www.eclipse.org/legal/epl-v10.html
 */
module TSDR {

    yang-version 1;

    namespace "opendaylight:TSDR";

    prefix TSDR;

    contact
      "YuLing Chen <yuling_c@dell.com>, Sharon Aicler <saichler@cisco.com>";

    description
      "YANG definition of TSDR Data Model.";

    revision "2015-02-19" {
      description
        "TSDR Data Model.";
    }

    typedef  DataCategory {
        description
            "Category of TSDR data.";
        type enumeration {
            enum FLOW_STATS;
            enum FLOW_TABLE_STATS;
            enum PORT_STATS;
            enum QUEUE_STATS;
            enum FLOW_GROUP_STATS;
            enum FLOW_METER_STATS;
            enum LOG_RECORDS;
            enum EXTERNAL;
            enum SYSLOG;
            enum NETFLOW;
            enum SNMP_INTERFACES;
            enum RESTCONF;
            enum ODL_LOG;
            enum YANG_NOTIFICATION;
        }
    }

    grouping Attribute{
        description
            "Attributes extracted from log record for data analysis purpose.";
        leaf name {
            description
                "Name of the attribute.";
            type string;
        }
        leaf value {
            description
                "Value of the attribute.";
            type string;
        }
    }

    grouping RecordKey{
        description
            "The keys of a TSDR record. For example, FlowTableID, FlowID, PortID
            are keys of OpenFlow statistics data.";
        leaf KeyName{
            description
                "The name of the key.";
            type string;
        }
        leaf KeyValue{
            description
                "The value of the key.";
            type string;
        }
    }

    grouping TSDRRecord{
        description
            "The base type of TSDR data.";
        leaf NodeID {
            description
                "The ID of the network element.";
            type string;
        }
        leaf TSDRDataCategory {
            description
                "The category of the TSDR data.";
            type DataCategory;
        }
        list RecordKeys{
            description
                "The key(s) of the TSDR data. For example, the Flow Table statistics data
                would have FlowID + TableID as the combination keys.";
            uses RecordKey;
        }
    }

    rpc purgeTSDRRecord {
        description
            "The API to purge a list of TSDRRecord with specified retention time.";
            input {
            leaf TSDRDataCategory {
                description
                    "The category of the TSDR data.";
                type DataCategory;
            }
            leaf retention_time{
                description
                    "The retention time of the TSDR data.";
                type int64;
            }
        }
    }

    rpc purgeAllTSDRRecord {
        description
            "The API to purge all TSDRRecord.";
            input {
            leaf retention_time{
                description
                    "The retention time of the TSDR data.";
                type int64;
            }
        }
    }
}
