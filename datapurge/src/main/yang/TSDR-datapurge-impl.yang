/*
 * Copyright (c) 2015 Dell Inc. and others.  All rights reserved.
 *
 * This program and the accompanying materials are made available under the
 * terms of the Eclipse Public License v1.0 which accompanies this distribution,
 * and is available at http://www.eclipse.org/legal/epl-v10.html
 */
module TSDR-datapurge-impl {

  yang-version 1;
  namespace "urn:opendaylight:params:xml:ns:yang:controller:config:TSDR-datapurge:impl";
  prefix "TSDR-datapurge-impl";

    import config { prefix config; revision-date 2013-04-05; }
    import opendaylight-md-sal-binding { prefix mdsal; revision-date 2013-10-28; }
    import rpc-context { prefix rpcx; revision-date 2013-06-17; }
    contact
      "YuLing Chen <yuling_c@dell.com>";
    description
        "This module contains the base YANG definitions for
        TSDR-datapurge-impl Implementation";

    revision "2015-09-25" {
        description
            "Initial revision.";
    }
    // This is the definition of the service implementation as a module identity.
    identity TSDR-datapurge-impl {
            base config:module-type;
            config:java-name-prefix TSDRDatapurge;
    }

    // Augments the 'configuration' choice node under modules/module.
    // We consume the three main services, RPCs, DataStore, and Notifications
    augment "/config:modules/config:module/config:configuration" {
        case TSDR-datapurge-impl {
            when "/config:modules/config:module/config:type = 'TSDR-datapurge-impl'";

            container rpc-registry {
                uses config:service-ref {
                    refine type {
                        mandatory true;
                        config:required-identity mdsal:binding-rpc-registry;
                    }
                }
            }

          container notification-service {
              uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }
        }
    }
}
