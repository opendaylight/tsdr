/*
 * Copyright (c) 2015 Cisco Systems, Inc. and others.  All rights reserved.
 *
 * This program and the accompanying materials are made available under the
 * terms of the Eclipse Public License v1.0 which accompanies this distribution,
 * and is available at http://www.eclipse.org/legal/epl-v10.html
 */
module tsdr-configuration {

    yang-version 1;
    namespace "urn:opendaylight:params:xml:ns:yang:controller:config:tsdr:configuration";
    prefix "tsdr-configuration";

    import config { prefix config; revision-date 2013-04-05; }
    import opendaylight-md-sal-binding { prefix mdsal; revision-date 2013-10-28; }

    contact
      "Sharon Aicler <saichler@gmail.com>";
    description
        "This module contains the base YANG definitions for
        tsdr-collector-spi impl implementation.";

    revision "2015-11-30" {
        description
            "Initial revision.";
    }

    // This is the definition of the service implementation as a module identity.
    identity tsdr-configuration {
            base config:module-type;
            config:java-name-prefix TSDRConfig;
    }
    augment "/config:modules/config:module/config:configuration" {
                case tsdr-configuration {
                    when "/config:modules/config:module/config:type = 'tsdr-configuration'";
                    container rpc-registry {
                        uses config:service-ref {
                            refine type {
                                mandatory true;
                                config:required-identity mdsal:binding-rpc-registry;
                            }
                        }
                    }
                }
            }

    rpc getProperty {
        input {
            leaf name {
                type string;
            }
        }
        output {
            leaf value {
                type string;
            }
        }
    }

    rpc getAllProperties {
        output {
            list properties {
                leaf key {
                    type string;
                }
                leaf value {
                   type string;
                }
            }
        }
    }
}
