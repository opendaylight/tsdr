/*
 * Copyright (c) 2016 TethrNet Technology Co.Ltd and others.  All rights reserved.
 * Copyright (c) 2016 Cisco Systems, Inc. and others.  All rights reserved.
 *
 * This program and the accompanying materials are made available under the
 * terms of the Eclipse Public License v1.0 which accompanies this distribution,
 * and is available at http://www.eclipse.org/legal/epl-v10.html
 */

module tsdr-syslog-collector {
    yang-version 1;
    namespace "urn:opendaylight:params:xml:ns:yang:controller:config:tsdr-syslog-collector";
    prefix "tsdr-syslog-collector";

    contact
      "Sharon Aicler <saichler@gmail.com>";
    description
        "This module contains the base YANG definitions for
        tsdr-syslog-collector impl implementation.";

    revision "2015-10-07" {
        description
            "Initial revision.";
    }

    container syslog-collector-config {
        leaf udpport {
            type uint16;
            default 514;
        }

        leaf tcpport {
            type uint16;
            default 6514;
        }

        leaf max-dispatcher-executor-pool-size {
            type uint16;
            default 10;
        }

        leaf max-dispatcher-executor-queue-size {
            type uint16;
            default 1000;
        }

        leaf max-dispatcher-notification-queue-size {
            type uint16;
            default 1000;
        }

        leaf store-flush-interval {
            type uint16;
            default 2500;
        }
    }

    typedef severity {
        type enumeration {
            enum EMERGENCY;
            enum ALERT;
            enum CRITICAL;
            enum ERROR;
            enum WARNING;
            enum NOTICE;
            enum INFORMATION;
            enum DEBUG;
        }

        description "Severity enumeration";
    }

    typedef facility {
        type enumeration {
            enum KERNEL;
            enum USER_LEVEL;
            enum MAIL;
            enum SYSTEM_DAEMON;
            enum SECURITY;
            enum SYSLOGD;
            enum LINE_PRINTER;
            enum NETWORK_NEWS;
            enum UUCP;
            enum CLOCK;
            enum SECURITY2;
            enum FTP;
            enum NTP;
            enum LOG_AUDIT;
            enum LOG_ALERTY;
            enum CLOCK2;
            enum LOCAL0;
            enum LOCAL1;
            enum LOCAL2;
            enum LOCAL3;
            enum LOCAL4;
            enum LOCAL5;
            enum LOCAL6;
            enum LOCAL7;
        }

        description "Facility enumeration";
    }

    grouping meta-filter {
        leaf severity {
            type severity;
        }
        leaf facility {
            type facility;
        }
        leaf sid {
            type string;
            default ".*";
            description "Messageid of syslog";
        }
        leaf host {
            type string;
            default ".*";
            description "Hostname of syslog";
        }
        leaf application {
            type string;
            default ".*";
            description "Application name of syslog";
        }
        leaf pid {
            type string;
            default ".*";
            description "Processid of syslog";
        }
        leaf content {
            type string;
            default ".*";
            description "Content Body of syslog";
        }
    }

    container syslog-dispatcher {
        list syslog-filter {
            config true;
            key "filter-id";
            leaf filter-id {
                type string;
                description "the unique ID of registered filter.";
            }

            container filter {
                uses meta-filter;
            }

            leaf callback-url {
                type string;
                mandatory true;
                description "callback URL of your app.";
            }
        }
    }
}
