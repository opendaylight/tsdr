/*
 * Copyright (c) 2016 Cisco Inc. and others.  All rights reserved.
 *
 * This program and the accompanying materials are made available under the
 * terms of the Eclipse Public License v1.0 which accompanies this distribution,
 * and is available at http://www.eclipse.org/legal/epl-v10.html
 */
module tsdr-sflow-statistics-collector {

    yang-version 1;
    namespace "urn:opendaylight:params:xml:ns:yang:controller:config:tsdr:sflow:statistics:collector";
    prefix "tsdr-sflow-statistics-collector";

    contact
      "YuLing Chen <yulingch@cisco.com>";
    description
        "This module contains the base YANG definitions for
        tsdr-sflow-statistics-collector impl implementation.";

    revision "2016-06-04" {
        description
            "Initial revision.";
    }

    container TSDRSFlowConfig{
       leaf polling-interval{
          type int64;
       }
    }

    rpc setPollingInterval  {
        description
          "set the polling interval of the collector";
        input {
            leaf interval {
              type int64;
              description "interval";
            }
        }
    }
}
