/*
 * Copyright (c) 2015 Cisco Systems, Inc. and others.  All rights reserved.
 *
 * This program and the accompanying materials are made available under the
 * terms of the Eclipse Public License v1.0 which accompanies this distribution,
 * and is available at http://www.eclipse.org/legal/epl-v10.html
 */
module tsdr-openflow-statistics-collector {

    yang-version 1;
    namespace "urn:opendaylight:params:xml:ns:yang:controller:config:tsdr:openflow:statistics:collector";
    prefix "tsdr-openflow-statistics-collector";

    contact
      "Sharon Aicler <saichler@gmail.com>";
    description
        "This module contains the base YANG definitions for
        tsdr-openflow-statistics-collector impl implementation.";

    revision "2015-08-20" {
        description
            "Initial revision.";
    }

    container TSDROSCConfig {
       leaf polling-interval {
          type int64;
          default 15000;
       }

       leaf record-store-batch-size {
           type int64;
           default 500;
        }
    }

    rpc setPollingInterval  {
        description
          "set the polling interval of the collector";
        input {
            leaf interval {
              type int64;
              description "interval";
            }
        }
    }
}
