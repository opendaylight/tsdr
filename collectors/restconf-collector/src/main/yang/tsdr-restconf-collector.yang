module tsdr-restconf-collector {

    yang-version 1;
    namespace "urn:opendaylight:params:xml:ns:yang:controller:config:tsdr:restconf:collector";
    prefix "tsdr-restconf-collector";

    import config { prefix config; revision-date 2013-04-05; }
    import opendaylight-md-sal-binding { prefix mdsal; revision-date 2013-10-28; }
    contact
      "AbdulRahman AlHamali <a.alhamali@saugo360.com>";
    description
        "This module contains the base YANG definitions for
        tsdr-restconf-collector impl implementation.";

    revision "2016-11-17" {
        description
            "Initial revision.";
    }

    // This is the definition of the service implementation as a module identity.
    identity tsdr-restconf-collector {
            base config:module-type;
            config:java-name-prefix TSDRRestconfCollector;
    }

    augment "/config:modules/config:module/config:configuration" {
        case tsdr-restconf-collector {
            when "/config:modules/config:module/config:type = 'tsdr-restconf-collector'";

            container rpc-registry {
                uses config:service-ref {
                    refine type {
                        mandatory true;
                        config:required-identity mdsal:binding-rpc-registry;
                    }
                }
            }
        }
    }
}
