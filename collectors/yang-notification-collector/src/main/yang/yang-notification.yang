module yang-notification {
    yang-version 1;
    namespace "urn:opendaylight:tsdr:yang:notification:collector:config";
    prefix "yang-notification";

    revision "2018-10-05" {
        description "Initial revision of yang notification model";
    }

    container notification-subscription {
        list notifications {

            key "notification";
            leaf notification {
               type string;
               config true;
               mandatory true;
            }
        }
    }
}
