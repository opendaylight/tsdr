/*
 * Copyright (c) 2015 Cisco Systems, Inc. and others.  All rights reserved.
 *
 * This program and the accompanying materials are made available under the
 * terms of the Eclipse Public License v1.0 which accompanies this distribution,
 * and is available at http://www.eclipse.org/legal/epl-v10.html
 */
module tsdr-external-collector-service {

    yang-version 1;
    namespace "urn:opendaylight:params:xml:ns:yang:controller:config:tsdr:controller:metrics:collector";
    prefix "tsdr-external-collector-service";

    import config { prefix config; revision-date 2013-04-05; }
    import opendaylight-md-sal-binding { prefix mdsal; revision-date 2013-10-28; }
    contact
      "Sharon Aicler <saichler@gmail.com>";
    description
        "This module contains the base YANG definitions for
        tsdr-external-collector-service impl implementation.";

    revision "2015-08-28" {
        description
            "Initial revision.";
    }

    // This is the definition of the service implementation as a module identity.
    identity tsdr-external-collector-service {
            base config:module-type;
            config:java-name-prefix TSDRECS;
    }

    augment "/config:modules/config:module/config:configuration" {
                case tsdr-external-collector-service {
                    when "/config:modules/config:module/config:type = 'tsdr-external-collector-service'";
                    container data-broker {
                        uses config:service-ref {
                            refine type {
                                mandatory false;
                                config:required-identity mdsal:binding-async-data-broker;
                            }
                        }
                    }
                    container rpc-registry {
                        uses config:service-ref {
                            refine type {
                                mandatory true;
                                config:required-identity mdsal:binding-rpc-registry;
                            }
                        }
                    }
                }
            }
}
