/*
 * Copyright (c) 2015 Tata Consultancy Service and others.  All rights reserved.
 *
 * This program and the accompanying materials are made available under the
 * terms of the Eclipse Public License v1.0 which accompanies this distribution,
 * and is available at http://www.eclipse.org/legal/epl-v10.html
 */
module tsdr-snmp-data-collector {

    yang-version 1;
    namespace "urn:opendaylight:params:xml:ns:yang:controller:config:tsdr:snmp:data:collector";
    prefix "tsdr-snmp-data-collector";
    import ietf-inet-types {
        prefix inet;
        revision-date 2013-07-15;
    }
    import IF-MIB {
        prefix if-mib;
    }
    contact
      "Trapti Khandelwal <trapti.khandelwal@tcs.com>";
    description
        "This module contains the base YANG definitions for
        tsdr-snmp-data-collector impl implementation.";

    revision "2015-10-13" {
        description
            "Initial revision.";
    }

    container TSDRSnmpDataCollectorConfig{
        leaf polling-interval {
            type int64;
            default 30000;
        }

        leaf store-metrics-executor-queue-size {
            type int64;
            default 100000;
        }
     }

    typedef snmp-metric {
        type enumeration {
         // enum MTU;        does not need to be stored since it does not change often
         // enum ifSpeed;    does not need to be stored since it does not change often
            enum ifInNUcastPkts;
            enum ifInDiscards;
            enum ifInErrors;
            enum ifInOctets;
            enum ifInUnknownProtos;
            enum ifInUcastPkts;
            enum ifOutQLen;
            enum ifOutNUcastPkts;
            enum ifOutErrors;
            enum ifOutDiscards;
            enum ifOutUcastPkts;
            enum ifOutOctets;
            enum ifOperStatus;
            enum ifAdminStatus;
        }
    }
}
