/*
 * Copyright (c) 2015 Cisco Systems, Inc. and others.  All rights reserved.
 *
 * This program and the accompanying materials are made available under the
 * terms of the Eclipse Public License v1.0 which accompanies this distribution,
 * and is available at http://www.eclipse.org/legal/epl-v10.html
 */
module tsdr-collector-spi {

    yang-version 1;
    namespace "urn:opendaylight:params:xml:ns:yang:controller:config:tsdr:collector:spi";
    prefix "tsdr-collector-spi";

    import TSDR {prefix TSDR;revision-date "2015-02-19";}
    import tsdr-metric-data { prefix tsdr-metric-data; revision-date 2016-03-25;}
    import tsdr-log-data { prefix tsdr-log-data; revision-date 2016-03-25;}

    contact
      "Sharon Aicler <saichler@gmail.com>";
    description
        "This module contains the base YANG definitions for
        tsdr-collector-spi impl implementation.";

    revision "2015-09-15" {
        description
            "Initial revision.";
    }

    rpc insertTSDRMetricRecord {
        description
            "The API to store a list of TSDRMetricRecord.";
             input {
                 leaf collector-code-name {
                      type string;
                 }
                 list TSDRMetricRecord{
                     uses tsdr-metric-data:TSDRMetric;
                 }
             }
    }
    rpc insertTSDRLogRecord {
        description
            "The API to store a list of TSDRLogRecord.";
             input {
                 leaf collector-code-name {
                      type string;
                 }
                 list TSDRLogRecord{
                     uses tsdr-log-data:TSDRLog;
                 }
             }
    }
}
