/*
 * Copyright (c) 2015 Cisco Systems, Inc. and others.  All rights reserved.
 *
 * This program and the accompanying materials are made available under the
 * terms of the Eclipse Public License v1.0 which accompanies this distribution,
 * and is available at http://www.eclipse.org/legal/epl-v10.html
 */
module tsdr-northbound-api {

    yang-version 1;
    namespace "urn:opendaylight:params:xml:ns:yang:controller:config:tsdr:northbound:api";
    prefix "tsdr-northbound-api";

    import config { prefix config; revision-date 2013-04-05; }
    import opendaylight-md-sal-binding { prefix mdsal; revision-date 2013-10-28; }
    contact
      "Sharon Aicler <saichler@gmail.com>";
    description
        "This module contains the base YANG definitions for
        tsdr-northbound-api implementation.";

    revision "2015-08-20" {
        description
            "Initial revision.";
    }

    // This is the definition of the service implementation as a module identity.
    identity tsdr-northbound-api {
            base config:module-type;
            config:java-name-prefix TSDRNBI;
    }
    augment "/config:modules/config:module/config:configuration" {
                case tsdr-northbound-api {
                    when "/config:modules/config:module/config:type = 'tsdr-northbound-api'";
                    container rpc-registry {
                        uses config:service-ref {
                            refine type {
                                mandatory true;
                                config:required-identity mdsal:binding-rpc-registry;
                            }
                        }
                    }
                }
            }

    rpc addMetric {
        description
          "Add a metric record to a specific metric";
        input {
            leaf name {
                type string;
            }
            leaf value {
                type string;
            }
            leaf nodeID {
              type string;
            }
            leaf path {
              type string;
            }
            leaf category{
              type int32;
            }
        }
    }
}
