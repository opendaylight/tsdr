/*
 * Copyright (c) 2015 Dell Inc. and others.  All rights reserved.
 *
 * This program and the accompanying materials are made available under the
 * terms of the Eclipse Public License v1.0 which accompanies this distribution,
 * and is available at http://www.eclipse.org/legal/epl-v10.html
 */
module TSDR-dataquery-impl {

  yang-version 1;
  namespace "urn:opendaylight:params:xml:ns:yang:controller:config:TSDR-dataquery:impl";
  prefix "TSDR-dataquery-impl";

    import tsdr-metric-data { prefix tsdr-metric-data; revision-date 2016-03-25;}
    import tsdr-log-data { prefix tsdr-log-data; revision-date 2016-03-25;}

    contact
      "YuLing Chen <yuling_c@dell.com>";
    description
        "This module contains the base YANG definitions for
        TSDR-dataquery-impl Implementation";

    revision "2015-02-19" {
        description
            "Initial revision.";
    }

    rpc addMetric {
        description
          "Add metric RPC method for external collectors";
        input {
            uses tsdr-metric-data:TSDRMetric;
        }
    }

    rpc addLog {
        description
          "Add log record RPC method for external collectors";
        input {
            uses tsdr-log-data:TSDRLog;
        }
    }
}
